package Bohnen_level_n_1{
	package Requirements{}
	package Use_Cases{}
	package Structure{
		package Functional_Structure{}
		package Logical_Structure{}
	}
	package Behavior{}
	package Interfaces_and_signals{
		package Functional{}
		package Logical{}
	}
}
