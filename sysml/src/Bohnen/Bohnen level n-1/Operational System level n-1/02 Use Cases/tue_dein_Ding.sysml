package 'tue_dein_Ding' {
	
	part def Bedrohung;
	part def Hungriger_Loewe;
	part def Bohnenfeld;
	part def Partner;
	
	
	
	use case def 'Vermehre dich' {	
	}
	
	use case def 'Ernähre dich' {
	}
	
	use case def 'schütze dich' {
	}
	
	use case def 'Lebe' {
}
}
